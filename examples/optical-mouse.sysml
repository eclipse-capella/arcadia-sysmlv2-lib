/*
 * Copyright (c) 2026 OBEO
 * This program and the accompanying materials
 * are made available under the terms of the Eclipse Public License v2.0
 * which accompanies this distribution, and is available at
 * https://www.eclipse.org/legal/epl-2.0/
 *
 * SPDX-License-Identifier: EPL-2.0
 *
 * Contributors:
 *     Obeo and Thales Global Services - initial implementation
 */
occurrence def <SE> OpticalMouseModel {
	metadata ArcadiaPackage {engineeringPerspective = ArcadiaEngineeringPerspective::SystemEngineering;}
    private import Arcadia::*;
	private import ScalarValues::Integer;
	private import ScalarValues::Boolean;
	private import SI::kg;
	private import SI::W;
	private import ModelingMetadata::*;
	private import RequirementDerivation::*;
	private import KerML::FeatureDirectionKind;

	package <OA> 'Operational Analysis' {
		metadata ArcadiaPackage {engineeringPerspective = ArcadiaEngineeringPerspective::OperationalAnalysis;}
		doc /* Defines the operational view of the system context and stakeholder needs.
		Captures missions, actors, and activities without technical constraints.
		Serves as the foundation for deriving system-level requirements. */
		package Functions {
			private import Data::*;
			action 'Root Function' : Function;
		}
		package Capabilities;
		package Interfaces;
		package Data;
		package Structure {
			private import Data::*;
			private import Functions::*;
		}
		package Requirements;
	}

	package <SA> 'System Analysis' {
		metadata ArcadiaPackage {engineeringPerspective = ArcadiaEngineeringPerspective::SystemAnalysis;}
		doc /* Defines the system’s intended behavior and responsibilities in response to stakeholder needs.
		Describes system functions, interfaces, and interactions, independently from implementation choices.
		Serves as a basis for the logical architecture. */
		package Functions {
			private import Data::*;
			action 'Root Function' : Function {
				allocation : Realization allocate OA::Functions::'Root Function' to self;
				action 'Move Cursor' : Function;
			}
		}
		package Capabilities;
		package Interfaces;
		package Data;
		package Structure {
			private import Data::*;
			private import Functions::*;
			part system : Component;
		}
		package Requirements {
			requirement <'SR1'> 'Cursor Control' {
				doc /* The user shall be able to move the cursor on the screen by moving the mouse. */
			}
		}
	}

	package <LA> 'Logical Architecture' {
		metadata ArcadiaPackage {engineeringPerspective = ArcadiaEngineeringPerspective::LogicalArchitecture;}
		doc /* Defines the logical architecture of the system.
		Contains logical components, functions, and their interactions, abstracted from implementation details.
		Serves as a bridge between system needs and physical design. */
		package Functions {
			private import Data::*;

			action 'Root Function' : Function {
				allocation : Realization allocate SA::Functions::'Root Function' to self;
	   	    	action 'Capture Movement' : Function {
	            	@StatusInfo {status = StatusKind::tbd;}
	   	    		//Corresponds to the description field in Capella
	        		doc description /*Interpret raw optical data into motion vectors.*/
	            	//Correspond to a Capella Function Output Port and the allocated Exchange Item(s) (binding rawOpticalData)
	            	out FOP1 [0..*] : ExchangeItem = (rawOpticalDataX, rawOpticalDataY);
	            	// Corresponds to a Capella Function Realization: this Logical Function realizes the System Function 'Move Cursor'.
	            	// The Realization is owned by the realizing element, which is designated by 'self'.
	            	allocation : Realization allocate SA::Functions::'Root Function'.'Move Cursor' to self;
	            	//Corresponds to a Capella Property Value Group and its Property Values (native Capella property values have no unit)
	            	attribute 'Safety' {
	            		attribute 'Safety Class' : Integer = 2;
	            		attribute 'Certified' : Boolean = false;
	            	}
	        	}

	   	    	action 'Transform Raw Optical Data' : Function {
	   	    		in FIP2 [0..*] : ExchangeItem = (rawOpticalDataX, rawOpticalDataY);
	   	    		// This Logical Function also realizes the System Function 'Move Cursor' (a System Function can be realized by several Logical Functions).
	   	    		allocation : Realization allocate SA::Functions::'Root Function'.'Move Cursor' to self;
	   	    	}

	   	    	// A Functional Exchange. Its payload is the Exchange Item(s) allocated to the exchange in Capella.
	   	    	flow 'Optical Data' : FunctionalExchange of :>> payload = (rawOpticalDataX, rawOpticalDataY)
	   	    		from 'Capture Movement'.FOP1 to 'Transform Raw Optical Data'.FIP2;

	   	    	// Binding the Exchange Item(s) to the flow
	   	    	//bind 'Optical Data'.payload = (rawOpticalDataX, rawOpticalDataY);


	   	    	// A Capella Function Package owned by a function: a package nested in the action
	   	    	package 'Motion Filtering' {
	   	    		action 'Filter Noise' : Function;
	   	    	}
	   	    }

			// A Capella Function Package: a plain nested package
			package 'Power Management' {
				action 'Manage Power' : Function;
			}
    	}

		package Capabilities {
			private import Functions::*;
			private import Structure::*;
			occurrence 'Move Cursor on Screen' : Capability  {
				ref action :>> involvedFunctions = ('Root Function'.'Capture Movement', 'Root Function'.'Transform Raw Optical Data');
				ref part :>> involvedComponents = (system.'Optical Sensor Unit', system.'Mouse Controller');

				// A Functional Chain owned by the Capability (as in Capella, where a Functional Chain can be owned
				// by a Function or by a Capability). A chain owned by the Capability is involved by construction:
				// involvedFunctionalChains only lists the chains owned elsewhere.
				action 'read movement' : FunctionalChain {
					ref flow :>> involvedFunctionalExchanges = ('Root Function'.'Optical Data');
					perform 'Root Function'.'Capture Movement';
					perform 'Root Function'.'Transform Raw Optical Data';

					succession first start then 'Root Function'.'Capture Movement';
					succession first 'Root Function'.'Capture Movement' then 'Root Function'.'Transform Raw Optical Data';
					succession first 'Root Function'.'Transform Raw Optical Data' then done;
				}
			}

			occurrence 'Provide Interface to User' : Mission  {
				ref occurrence :>> exploitedCapabilities = ('Move Cursor on Screen');
				ref part :>> involvedComponents = (system.'Optical Sensor Unit', system.'Mouse Controller');
			}

			// A Capella Capability Package
			package 'Maintenance';
		}
		// A Capella Interface Package
		package Interfaces {
			package 'User Interfaces';
		}
		package Data {
   	    	item rawOpticalDataX: ExchangeItem;
   	    	item rawOpticalDataY: ExchangeItem;
			// A Capella Data Package
			package 'Status Data' {
				item batteryLevel : ExchangeItem;
			}
		}
		package Structure {
			private import Functions::*;
			private import Data::*;
			// A Capella Component Package (here for actors)
			package 'External Actors' {
				part technician : Component {
					:>> isActor = true;
				}
			}
			part computerUser : Component {
				:>> isActor = true;
			}

			part system : Component{
				// Corresponds to a Capella Component Realization: the Logical system realizes the System Analysis system.
				allocation : Realization allocate SA::Structure::system to self;

				part 'Optical Sensor Unit' : Component {
				    doc description /*Captures surface movement using optical detection.*/
	                :>> isActor = false;
	                :>> isHuman = false;
	                perform 'Root Function'.'Capture Movement';
	                port 'Cable Connector' : ComponentPort  {
		               	out [0..*] : ExchangeItem = (rawOpticalDataX, rawOpticalDataY);
		               	:>> portDirection = FeatureDirectionKind::'out';
		               	ref item :>> allocatedFunctionPorts = ('Root Function'.'Capture Movement'.FOP1);
	                }
			 	}

				part 'Mouse Controller' : Component {
	                doc description /*Manages mouse peripherals*/
	                // A Capella Component Package owned by a component: a package nested in the part
	                package 'Mechanical Parts' {
	                	part 'Mouse Casing' : Component;
	                }
	                :>> isActor = false;
	                :>> isHuman = false;
	                perform 'Root Function'.'Transform Raw Optical Data';
	                port 'Cable Connector' : ComponentPort {
		               	in [0..*] : ExchangeItem = (rawOpticalDataX, rawOpticalDataY);
		               	:>> portDirection = FeatureDirectionKind::'in';
		               	ref item :>> allocatedFunctionPorts = ('Root Function'.'Transform Raw Optical Data'.FIP2);
	                }
			 	}

				// An interface between 2 components Ports
				interface cable : ComponentExchange
					connect 'Optical Sensor Unit'.'Cable Connector' to 'Mouse Controller'.'Cable Connector' {
					flow system.'Optical Sensor Unit'.'Cable Connector' to system.'Mouse Controller'.'Cable Connector';
			        ref item :>> allocatedExchangeItems = (rawOpticalDataX, rawOpticalDataY);
	        		// A Functional Exchange allocated to this Component Exchange (Capella: ComponentExchangeFunctionalExchangeAllocation).
	        		// The allocation is owned by the Component Exchange, which is designated by 'self'.
	        		allocation : ExchangeAllocation allocate 'Root Function'.'Optical Data' to self;
					}
			}
		}

		package Requirements {
			// 'R1' and 'R1.1' are the IDs (short names) of the requirements.
			// Nesting only organizes the requirements, it is not a trace.
			requirement <'R1'> 'Movement Capture' {
				doc /* The mouse shall capture the movement of the user. */
				requirement <'R1.1'> Optical {
					doc /* The mouse should capture movement using optical detection */
				}
			}
			// A derivation is a trace between requirements, here from the system analysis to the logical architecture
			#derivation connection {
				end #original ::> SA::Requirements::'Cursor Control';
				end #derive ::> 'Movement Capture';
			}
		}
	}

	package <PA> 'Physical Architecture' {
		metadata ArcadiaPackage {engineeringPerspective = ArcadiaEngineeringPerspective::PhysicalArchitecture;}
		doc /* Defines the physical components and their interactions that realize the logical architecture.
		Includes hardware, software, and communication elements, with consideration for implementation constraints.
		Supports integration, validation, and preparation for deployment. */
		package Functions {
			private import Data::*;
			action 'Root Function' : Function {
				allocation : Realization allocate LA::Functions::'Root Function' to self;
			}
		}
		package Capabilities;
		package Interfaces;
		package Data;
		package Structure {
			private import Data::*;
			private import Functions::*;
			part system : Component{
				allocation : Realization allocate LA::Structure::system to self;

				part 'Optical Sensor Module' : BehaviorComponent {
				    doc description /*Captures surface movement using optical detection.*/
	                // The Optical Sensor Module satisfies the requirement; the satisfy is owned by the satisfying element
	                satisfy LA::Requirements::'Movement Capture'.Optical;
	                :>> isActor = false;
	                :>> isHuman = false;
	                //A Property Value in a model created in SysML v2 carries its unit. The description of a property value is a doc.
	                attribute 'Mass' = 0.4 [kg] {
	                	doc description /*Mass of the module without cable.*/
	                }
	                attribute 'Budget' {
	                	attribute 'Power' = 2.5 [W];
	                }
	            }

				// Another Physical Behavior Component: embedded software.
				part 'Mouse Firmware' : BehaviorComponent {
				    doc description /*Embedded software interpreting the raw optical data into motion vectors.*/
				}

				// A Physical Node Component: it hosts the two Behavior Components, which are deployed on it (not contained in it).
				// The Deployments are stored in the Node, which is designated by 'self'.
				part 'Mouse PCB' : NodeComponent {
				    doc description /*Printed circuit board hosting the mouse electronics and software.*/
				    allocation : Deployment allocate system.'Optical Sensor Module' to self;
				    allocation : Deployment allocate system.'Mouse Firmware' to self;
				}

				// Another Physical Node Component: the Node 'Mouse PCB' is deployed on it, instead of being contained in it.
				part 'Mouse Casing' : NodeComponent {
				    doc description /*Casing of the mouse, which hosts the printed circuit board.*/
				    allocation : Deployment allocate system.'Mouse PCB' to self;
				}
	        }
		}
		package Requirements;
	}

	package <EPBS> 'EPBS Architecture' {
		metadata ArcadiaPackage {engineeringPerspective = ArcadiaEngineeringPerspective::EPBS;}
		doc /* Defines the configuration of the system as delivered to the customer.
		Describes the breakdown of end products, including deliverable items, versions, and traceability to physical components and requirements.
		Supports verification, acceptance, and product management. */
		package Functions {
			private import Data::*;
			action 'Root Function' : Function;
		}
		package Capabilities;
		package Interfaces;
		package Data;
		package Structure {
			private import Data::*;
			private import Functions::*;
			part system : Component {
				allocation : Realization allocate PA::Structure::system to self;
			}
		}
		package Requirements;
	}
}
